module srl_nokia-qos {
  yang-version 1.1;
  namespace "urn:srl_nokia/qos";
  prefix srl_nokia-qos;

  import srl_nokia-common {
    prefix srl_nokia-comm;
  }
  import srl_nokia-extensions {
    prefix srl_nokia-ext;
  }
  import srl_nokia-interfaces {
    prefix srl_nokia-if;
  }
  import srl_nokia-features {
    prefix srl-feat;
  }
  import srl_nokia-qos-policers {
    prefix srl_nokia-qos-policers;
  }
    import srl_nokia-fss-extensions {
        prefix srl_nokia-fss-ext;
    }

  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef traffic-class {
    type uint8 {
      range "0..7";
    }
  }

  typedef dot1p-value {
    type uint8 {
      range "0..7";
    }
  }

  typedef drop-probability {
    description
      "The various drop probability classifications that can be applied to a packet";
    type enumeration {
      enum low {
        description
          "Traffic that should be dropped last when there is congestion. Internally this is traffic that is colored green.";
      }
      enum medium {
        description
          "Traffic that should be dropped before green traffic but after red traffic when there is congestion. Internally this is traffic that is colored yellow.";
      }
      enum high {
        description
          "Traffic that should be dropped first when there is congestion. Internally this is traffic that is colored red.";
      }
    }
  }

  typedef ecn-drop-probability {
    description
      "The various drop probability classifications that can apply to an ECN slope";
    type enumeration {
      enum low {
        if-feature "srl-feat:platform-7220-d2 or srl-feat:platform-7220-d3 or srl-feat:platform-7220-d5 or srl-feat:platform-7220-h2 or srl-feat:platform-7220-h3 or srl-feat:platform-7220-h4";
        description
          "Traffic that should be dropped last when there is congestion. Internally this is traffic that is colored green.";
      }
      enum medium {
        if-feature "srl-feat:platform-7220-d2 or srl-feat:platform-7220-d3 or srl-feat:platform-7220-d5 or srl-feat:platform-7220-h2 or srl-feat:platform-7220-h3 or srl-feat:platform-7220-h4";
        description
          "Traffic that should be dropped before green traffic but after red traffic when there is congestion. Internally this is traffic that is colored yellow.";
      }
      enum high {
        if-feature "srl-feat:platform-7220-d2 or srl-feat:platform-7220-d3 or srl-feat:platform-7220-d5 or srl-feat:platform-7220-h2 or srl-feat:platform-7220-h3 or srl-feat:platform-7220-h4";
        description
          "Traffic that should be dropped first when there is congestion. Internally this is traffic that is colored red.";
      }
      enum all {
        if-feature "srl-feat:jericho2 or srl-feat:jericho2cp";
        description
          "All traffic, consisting of traffic marked low, medium and high drop-probability.";
      }
    }
  }

  typedef fp5c-cbs-size {
    description
      "Output-queue CBS values on FP5-c chipset.";
    type enumeration {
      enum default {
        description
          "Default CBS value";
      }
      enum alt-1 {
        description
          "CBS value corresponding to ALT-1 configuration";
      }
      enum alt-2 {
        description
          "CBS value corresponding to ALT-2 configuration";
      }
      enum alt-3 {
        description
          "CBS value corresponding to ALT-3 configuration";
      }
    }
  }

  typedef rewrite-profile {
    description
      "Profile-names for different profiles used during egress re-marking";
    type enumeration {
      enum in-plus {
        if-feature "srl-feat:future-0-0";
        description
          "The highest priority profile";
      }
      enum in {
        if-feature "srl-feat:future-0-0";
        description
          "The second level priority profile";
      }
      enum out {
        if-feature "srl-feat:future-0-0";
        description
          "The lowest level priotity profile";
      }
      enum exceed {
        if-feature "srl-feat:future-0-0";
        description
          "The third level priority profile";
      }
    }
  }

  typedef scheduler-level {
    description
      "Type for identifying the different scheduler hierarchy levels";
    type uint8 {
      range "1..4";
    }
  }

  typedef scheduler-node-id {
    description
      "Type for assignment of a unique ID to each scheduler node at a particular scheduler level/tier";
    type uint8 {
      range "0..11";
    }
  }

  typedef queue-type {
    description
      "Type of traffic serviced by a queue.";
    type enumeration {
      enum unicast;
      enum multicast;
    }
  }

  grouping qos-top {
    description
      "Top-level grouping for QoS model";
    container qos {
      srl_nokia-ext:first-released "19.11.1";
      if-feature "not srl-feat:platform-7220-d1";
      description
        "Top-level container for QoS data";
      uses ecn-top;
      uses queue-names-config;
      uses forwarding-classes-config;
      uses out-class-map-config {
        if-feature "srl-feat:future-0-0";
      }
      uses srl_nokia-qos-policers:policers-top {
        if-feature "srl-feat:future-0-0";
      }
      uses fp5c-global-tables {
        if-feature "srl-feat:future-0-0";
      }
      uses srl_nokia-qos-policers:policer-templates-top {
        if-feature "srl-feat:ingress-subif-policing";
      }
      uses queue-templates-top {
        if-feature "not srl-feat:future-0-0";
      }
      uses qos-classifier-top;
      uses qos-rewrite-top;
      uses scheduler-policies-top {
        if-feature "srl-feat:scheduler-policies";
      }
    }
  }

  grouping queue-names-config {
    container queues {
      description
        "Enclosing container for the list of user-defined queue names";
      list queue {
        key "name";
        description
          "List of user-defined queues";
        leaf name {
          type srl_nokia-comm:name;
          description
            "User-defined name of the queue

             The following queue names are the system-reserved default queue names on 7250 IXR systems:
             unicast-0
             unicast-1
             unicast-2
             unicast-3
             unicast-4
             unicast-5
             unicast-6
             unicast-7

             The following queue names are the system-reserved default queue names on FP5-c chipset based systems:
             queue-0
             queue-1
             queue-2
             queue-3
             queue-4
             queue-5
             queue-6
             queue-7
             queue-8
             queue-9
             queue-10
             queue-11
             queue-12
             queue-13
             queue-14
             queue-15";
          must "not (re-match(.,'unicast-[0-7]') or re-match(.,'multicast-[0-7]'))" {
              error-message "queue name reserved";
          }

        }
        leaf queue-index {
          if-feature "srl-feat:future-0-0";
          mandatory true;
          type uint16 {
            range "0..15";
          }
          description
            "The queue index (offset). If this value is not specified it is derived from the forwarding-class mapping (based on the forwarding-class-index).";
        }
      }
    }
  }

  grouping forwarding-classes-config {
    container forwarding-classes {
      description
        "Enclosing container for list of user-defined forwarding class names";
      list forwarding-class {
        key "name";
        leaf name {
          type srl_nokia-comm:name;
          description
            "User-defined name of the forwarding class

             The following forwarding-class names are the system-reserved default FC names on 7250 IXR systems:
             fc0
             fc1
             fc2
             fc3
             fc4
             fc5
             fc6
             fc7

             In addition to fc0-fc7, the following forwarding-class names are also system-reserved default FC names on FP5-c based platforms
             fc8
             fc9
             fc10
             fc11
             fc12
             fc13
             fc14
             fc15";
          must "not (re-match(.,'fc[0-7]'))" {
              error-message "forwaring-class name reserved";
          }

        }
        leaf forwarding-class-index {
          if-feature "srl-feat:jericho2 or srl-feat:jericho2cp";
          mandatory true;
          type uint8 {
            range "0..15";
          }
          description
            "Associates the forwarding class name with an index representing the forwarding-class-index. Forwarding classes with a higher forwarding-class-index are generally (subject to scheduler configuration) serviced more preferentially than forwarding classes with a lower forwarding-class-index.

             For the system-reserved default forwarding classes:
             fc0 -> forwarding-class-index = 0
             fc1 -> forwarding-class-index = 1
             fc2 -> forwarding-class-index = 2
             fc3 -> forwarding-class-index = 3
             fc4 -> forwarding-class-index = 4
             fc5 -> forwarding-class-index = 5
             fc6 -> forwarding-class-index = 6
             fc7 -> forwarding-class-index = 7
             fc8 -> forwarding-class-index = 8
             fc9 -> forwarding-class-index = 9
             fc10 -> forwarding-class-index = 10
             fc11 -> forwarding-class-index = 11
             fc12 -> forwarding-class-index = 12
             fc13 -> forwarding-class-index = 13
             fc14 -> forwarding-class-index = 14
             fc15 -> forwarding-class-index = 15";
        }
        container input {
          if-feature "srl-feat:future-0-0";
          leaf unicast-policer {
            type leafref {
              path "../../../../policers/policer/name";
            }
          }
          leaf unknown-unicast-policer {
            type leafref {
              path "../../../../policers/policer/name";
            }
          }
          leaf broadcast-policer {
            type leafref {
              path "../../../../policers/policer/name";
            }
          }
          leaf multicast-policer {
            type leafref {
              path "../../../../policers/policer/name";
            }
          }
        }
        container output {
          if-feature "srl-feat:jericho2 or srl-feat:jericho2cp";
          leaf queue {
            if-feature "srl-feat:future-0-0";
            mandatory true;
            type leafref {
              path "../../../../queues/queue/name";
            }
            description
              "Output queue for this forwarding class.";
          }
          leaf unicast-queue {
            if-feature "not srl-feat:future-0-0";
            must '. != ../multicast-queue';
            mandatory true;
            type leafref {
              path "../../../../queues/queue/name";
            }
            description
              "Output queue for unicast packets within this forwarding class

               For the system-reserved default forwarding classes:
               fc0 -> unicast-queue = unicast-queue0
               fc1 -> unicast-queue = unicast-queue1
               fc2 -> unicast-queue = unicast-queue2
               fc3 -> unicast-queue = unicast-queue3
               fc4 -> unicast-queue = unicast-queue4
               fc5 -> unicast-queue = unicast-queue5
               fc6 -> unicast-queue = unicast-queue6
               fc7 -> unicast-queue = unicast-queue7";
          }
          leaf multicast-queue {
            if-feature "not srl-feat:future-0-0";
            mandatory true;
            type leafref {
              path "../../../../queues/queue/name";
            }
            description
              "Output queue for multicast packets within this forwarding class.";
          }
        }
      }
    }
  }

  grouping out-class-map-config {
    list out-class-map {
      key "name";
      leaf name {
        type srl_nokia-comm:name;
        description
          "User defined out-class-map name";
      }
      list forwarding-class {
        key "name";
        leaf name {
          type union {
            type leafref {
              path "/srl_nokia-qos:qos/srl_nokia-qos:forwarding-classes/srl_nokia-qos:forwarding-class/srl_nokia-qos:name";
            }
            type srl_nokia-comm:default-forwarding-class;
          }
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        container queue {
          choice local-or-remote {
            case local {
              leaf queue-name {
                type union {
                  type leafref {
                    path "/srl_nokia-qos:qos/srl_nokia-qos:queues/srl_nokia-qos:queue/srl_nokia-qos:name";
                  }
                  type srl_nokia-comm:default-queue-name;
                }
                description
                  "The output-queue name";
                must "/srl_nokia-qos:qos/srl_nokia-qos:queues/srl_nokia-qos:queue[srl_nokia-qos:name=current()]/srl_nokia-qos:name = current() or
                       re-match(.,'queue-[0-7]')" {
                  error-message "queue doesn't exist";
                }
              }
            }
            case remote {
              leaf re-direct-to {
                type enumeration {
                  enum interface-queue;
                }
                description
                  "The re-direction to interface level queue";
              }
            }
          }
        }
      }
    }
  }

  grouping ecn-top {
    container explicit-congestion-notification {
      if-feature "not srl-feat:future-0-0";
      srl_nokia-ext:first-released "20.12.1";
      presence "When present ECN marking is enabled globally (on all interfaces)";
      leaf ecn-dscp-policy {
        if-feature "srl-feat:jericho2 or srl-feat:jericho2cp";
        mandatory true;
        description
          "Reference to the DSCP rewrite policy to use when DSCP rewrite is required as a side effect of ECN remarking.

           This is required configuration in order to globally enable ECN on J2 platforms.";
        type leafref {
          path "../../rewrite-rules/dscp-policy/name";
        }
      }
    }
  }

  grouping fp5c-global-tables {
    container cbs-size-table {
      leaf default-size {
        type uint64;
        description
          "Default cbs-size";
      }
      leaf alt-1 {
        type uint64;
        description
          "ALT-1 cbs-size";
      }
      leaf alt-2 {
        type uint64;
        description
          "ALT-2 cbs-size";
      }
      leaf alt-3 {
        type uint64;
        description
          "ALT-3 cbs-size";
      }
    }
    container resource-management {
      container resource-priority {
        description
          "Defines priority per forwarding-class and per profile to be used for access to shared chipset resources";
        list forwarding-class {
          key "name";
          leaf name {
            type union {
              type leafref {
                path "/srl_nokia-qos:qos/srl_nokia-qos:forwarding-classes/srl_nokia-qos:forwarding-class/srl_nokia-qos:name";
              }
              type srl_nokia-comm:default-forwarding-class;
            }
            must "/srl_nokia-qos:qos/srl_nokia-qos:forwarding-classes/srl_nokia-qos:forwarding-class[srl_nokia-qos:name = current()]/srl_nokia-qos:name = current() or
                  re-match(.,'fc[0-7]')" {
              error-message "forwarding-class doesn't exist";
            }
          }
          list profile {
            key "profile-name";
            leaf profile-name {
              type srl_nokia-comm:classify-profile;
            }
            leaf unicast-resource-priority {
              type uint8 {
                range "0..3";
              }
            }
            leaf multicast-resource-priority {
              type uint8 {
                range "0..3";
              }
            }
          }
        }
      }
      container drop-levels {
        list unicast {
          key "index";
          leaf index {
            type uint8 {
              range "0..3";
            }
          }
          leaf segment {
            type uint8 {
              range "0..3";
            }
          }
          leaf vpid {
            type uint8 {
              range "0..3";
            }
          }
          leaf header {
            type uint8 {
              range "0..15";
            }
          }
        }
        list multicast {
          key "index";
          leaf index {
            type uint8 {
              range "0..3";
            }
          }
          leaf segment {
            type uint8 {
              range "0..3";
            }
          }
          leaf vpid {
            type uint8 {
              range "0..3";
            }
          }
          leaf header {
            type uint8 {
              range "0..15";
            }
          }
        }
      }
      container untilization-levels {
        container segment-congestion {
          list level {
            key "index";
            leaf index {
              type uint8 {
                range "0..3";
              }
            }
            leaf threshold {
              type uint8 {
                range "0..127";
              }
            }
          }
        }
      }
    }
  }

  grouping queue-templates-top {
    container queue-templates {
      srl_nokia-ext:first-released "20.12.1";
      if-feature "not srl-feat:future-0-0";
      list queue-template {
        max-elements 64;
        description
          "List of queue templates that can be applied to egress queues or VOQ sets

           7250 IXR-6/10 supports a maximum 8 queue-templates. 7220-D2/D3/D5/H2/H3 supports a maximum of 64 queue-templates.";
        key "name";
        leaf name {
          type srl_nokia-comm:name;
          description
            "The name of the queue template

             The queue template with the special name 'default' is used when a queue-template reference is missing.";
        }
        container queue-depth {
          leaf maximum-burst-size {
            type uint32;
            units "bytes";
            default "0";
            description
              "Maximum amount of shared buffer memory available to the queue.

               On IXR-6/10 this parameter applies to a set of VOQs. If the configured value is 0 or no value is configured the limit is 256 MB (268435456 bytes), however the use of 'alpha' may limit the effective value to less than 256 MB. A configured non-zero value sets a static limit without 'alpha'.

               On 7220-D2/D3/D5/H2/H3 this parameter applies to an egress queue and the default value of zero instructs the forwarding chip to apply its own limit based on 'alpha'. A non-zero value disables 'alpha'. The alpha value  is 5 (0.25 multiplier of shared buffer space) for unicast queues and 4 (0.125 multiplier of shared buffer space) for multicast queues.

               Must be non-zero/non-default in order to add the active-queue-management presence container.";
          }
          leaf high-threshold-bytes {
            if-feature "not srl-feat:platform-7220-d5";
            type uint32;
            must '. <= ../maximum-burst-size';
            default "0";
            description
              "The queue depth that, when crossed in a rising direction, triggers a hardware interrupt and a recording of the current system time.

               The default value of 0 disables the functionality.

               On IXR-6/10 this parameter applies to a set of VOQs (and therefore to unicast traffic only). On 7220-D2/D3/H2/H3 this parameter applies to a unicast queue only; the configuration of this leaf is ignored when the queue-template is attached to a queue with queue-type other than unicast.

               On 7220-D2/D3 the threshold is rounded up the nearest multiple of 2048 bytes. On IXR-6/10 the threshold is rounded up to the nearest multiple of 4096 bytes. On 7220-H2/H3 the threshold is rounded up to the nearest multiple of 254 bytes.";
          }
        }
        container active-queue-management {
          presence "Presence container for WRED and/or ECN slopes. On 7220-D2/D3/D5/H2/H3, this container cannot be present to use the queue-template with a multicast queue.";
          leaf weight-factor {
            type uint8 {
              range "0..15";
            }
            default "0";
            description
              "Weight factor to use in the calculation of the current (average weighted) queue depth.";
          }
          list wred-slope {
            description
              "List of WRED slopes.";
            key "traffic-type drop-probability";
            leaf traffic-type {
              description
                "The traffic type to which the WRED slope applies.";
              type enumeration {
                enum tcp {
                  if-feature "srl-feat:platform-7220-d2 or srl-feat:platform-7220-d3 or srl-feat:platform-7220-d5 or srl-feat:platform-7220-h2 or srl-feat:platform-7220-h3 or srl-feat:platform-7220-h4";
                  description
                    "Refers to IPv4/IPv6 packets with a protocol/next-header indicating a value of 6.";
                }
                enum non-tcp {
                  if-feature "srl-feat:platform-7220-d2 or srl-feat:platform-7220-d3 or srl-feat:platform-7220-d5 or srl-feat:platform-7220-h2 or srl-feat:platform-7220-h3 or srl-feat:platform-7220-h4";
                  description
                    "Refers to all packets that are not IPv4/IPv6 packets with a protocol/next-header indicating a value of 6.";
                }
                enum all {
                  if-feature "srl-feat:jericho2 or srl-feat:jericho2cp";
                  description
                    "Refers to all traffic, whether it is TCP or non-TCP.";
                }
              }
            }
            leaf drop-probability {
              description
                "The drop probability to which the WRED slope applies.";
              type drop-probability;
            }
            leaf min-threshold-percent {
              type srl_nokia-comm:percentage;
              default "100";
              description
                "The percentage of the MBS that corresponds to the WRED mininum threshold parameter.

                 A slope is disabled by setting min-threshold-percent=100, max-threshold-percent=100 and max-probability=0";
            }
            leaf max-threshold-percent {
              type srl_nokia-comm:percentage;
              must '. >= ../min-threshold-percent';
              default "100";
              description
                "The percentage of the MBS that corresponds to the WRED maximum threshold parameter.

                 A slope is disabled by setting min-threshold-percent=100, max-threshold-percent=100 and max-probability=0";
            }
            leaf max-probability {
              type srl_nokia-comm:percentage;
              default "0";
              description
                "The maximum probability of dropping a packet (at or above the max-threshold).

                 A slope is disabled by setting min-threshold-percent=100, max-threshold-percent=100 and max-probability=0";
            }
          }
          list ecn-slope {
            description
              "List of ECN slopes.";
            key "ecn-drop-probability";
            leaf ecn-drop-probability {
              description
                "The drop probability to which the ECN slope applies.";
              type ecn-drop-probability;
            }
            leaf min-threshold-percent {
              type srl_nokia-comm:percentage;
              default "100";
              description
                "The percentage of the MBS that corresponds to the ECN mininum threshold parameter.

                 A slope is disabled by setting min-threshold-percent=100, max-threshold-percent=100 and max-probability=0.";
            }
            leaf max-threshold-percent {
              type srl_nokia-comm:percentage;
              must '. >= ../min-threshold-percent';
              default "100";
              description
                "The percentage of the MBS that corresponds to the ECN maximum threshold parameter.

                 A slope is disabled by setting min-threshold-percent=100, max-threshold-percent=100 and max-probability=0.";
            }
            leaf max-probability {
              type srl_nokia-comm:percentage;
              default "0";
              description
                "The maximum probability of marking a packet (at or above the max-threshold).

                 On 7220-D2/D3/D5/H2/H3 max-probability has a limited set of discrete values: 1,2,3,4,5,6,7,8,9,10,25,50,75,100. The user is allowed to enter any value but the system will choose the next-highest value that is supported.

                 A slope is disabled by setting min-threshold-percent=100, max-threshold-percent=100 and max-probability=0.";
            }
          }
        }
      }
    }
  }

  grouping scheduler-policies-top {
    container scheduler-policies {
      description
        "Container for the list of configured scheduler policies.";
      list scheduler-policy {
        key "name";
        description
          "List of scheduler policies. A scheduler policy is a set of schedulers that are to be applied together. Each scheduler within a scheduler policy takes an input, and outputs it according to a scheduling discipline that is specified within it.";
        leaf name {
          type srl_nokia-comm:name;
          description
            "Name for the scheduler policy.";
        }
        list scheduler {
          key "sequence";
          description
            "List of defined QoS traffic schedulers.";
          leaf sequence {
            type uint32 {
              range "0..1";
            }
            description
              "Sequence number for the scheduler within the scheduler policy. Schedulers are processed from lowest sequence to highest.";
          }
          leaf priority {
            type enumeration {
              enum strict {
                description
                  "This scheduler term is considered as a strict priority term - such that packets that arrive in the queue are immediately serviced.";
              }
            }
            description
              "Priority of the scheduler within the scheduler policy.";
          }
          list input {
            key "id";
            description
              "List of input sources for the scheduler.";
            leaf id {
              type string;
              description
                "User-defined identifier for the scheduler input";
            }
            leaf queue {
              mandatory true;
              description
                "The queue that is the input to the scheduler";
              type union {
                type leafref {
                  path "../../../../../queues/queue/name";
                }
                type srl_nokia-comm:default-queue-name;
              }
            }
            leaf weight {
              type uint8;
              description
                "For weighted round-robin schedulers, this leaf indicates the weight of the corresponding input.";
            }
          }
        }
      }
    }
  }

  grouping qos-classifier-top {
    description
      "Top-level grouping for classifier data";
    container classifiers {
      srl_nokia-ext:first-released "19.11.1";
      uses vxlan-classifier {
        if-feature "not srl-feat:future-0-0";
      }
      uses ip-classifier;
      uses mpls-tc-classifier;
      uses ethernet-classifier;
      uses egress-reclassification {
        if-feature "srl-feat:future-0-0";
      }
    }
  }

  grouping egress-reclassification {
    list dscp-reclassify-policy {
      description
        "Egress DSCP reclassification policy.";
      key "name";
      leaf name {
        type srl_nokia-comm:name;
        description
          "Name of egress dscp-reclassifier policy.";
      }
      list dscp {
        key "value";
        leaf value {
          type srl_nokia-comm:dscp-value;
        }
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class to which the DSCP value is mapped";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        leaf profile {
          if-feature "srl-feat:future-0-0";
          type srl_nokia-comm:classify-profile;
          description
            "The profile to which the DSCP value is mapped";
        }
      }
    }
  }

  grouping vxlan-classifier {
    leaf vxlan-default {
      if-feature "srl-feat:platform-7220-d2 or srl-feat:platform-7220-d3 or srl-feat:platform-7220-d5";
      type leafref {
        path "/srl_nokia-qos:qos/srl_nokia-qos:classifiers/srl_nokia-qos:dscp-policy/name";
      }
      description
        "Reference to the name of a DSCP mapping policy that applies to terminating VXLAN packets.";
    }
  }

  grouping ip-classifier {
    list dscp-policy {
      key "name";
      leaf name {
        type srl_nokia-comm:name;
        description
          "User-configured name for a DSCP mapping policy

           The name 'default' is reserved for the system default DSCP mapping policy.";
      }
      list dscp {
        key "value";
        leaf value {
          type srl_nokia-comm:dscp-value;
        }
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class to which the DSCP value is mapped";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        leaf drop-probability {
          srl_nokia-ext:first-released "20.12.1";
          if-feature "not srl-feat:future-0-0";
          type drop-probability;
          description
            "The drop probability to which the DSCP value is mapped";
        }
        leaf profile {
          if-feature "srl-feat:future-0-0";
          type srl_nokia-comm:classify-profile;
          description
            "The profile to which the DSCP value is mapped";
        }
        leaf de-out-profile {
          if-feature "srl-feat:future-0-0";
          type boolean;
          default "true";
          description
            "The discard-eligibility to which the DSCP value is mapped";
        }
        leaf ip-remark-policy {
          if-feature "srl-feat:future-0-0";
          description
            "The ip-remark-policy to be used for this dscp-value";
          type leafref {
            path "../../../../rewrite-rules/ip-remark-policy/name";
          }
        }
      }
    }
  }

  grouping mpls-tc-classifier {
    list mpls-traffic-class-policy {
      if-feature "srl-feat:jericho2 or srl-feat:jericho2cp or srl-feat:future-0-0";
      key "name";
      leaf name {
        type srl_nokia-comm:name;
        description
          "User-configured name for an MPLS traffic-class mapping policy

           The name 'default' is reserved for the system default MPLS TC mapping policy.";
      }
      list traffic-class {
        key "value";
        leaf value {
          type traffic-class;
          description
            "A single traffic-class value";
        }
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class to which the MPLS traffic-class value is mapped";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        leaf drop-probability {
          srl_nokia-ext:first-released "21.6.3";
          if-feature "not srl-feat:future-0-0";
          type drop-probability;
          description
            "The drop probability to which the traffic-class value is mapped";
        }
        leaf profile {
          if-feature "srl-feat:future-0-0";
          type srl_nokia-comm:classify-profile;
          description
            "The profile to which the DSCP value is mapped";
        }
        leaf de-out-profile {
          if-feature "srl-feat:future-0-0";
          type boolean;
          default "true";
          description
            "The discard-eligibility to which the DSCP value is mapped";
        }
        leaf ip-remark-policy {
          if-feature "srl-feat:future-0-0";
          description
            "The ip-remark-policy to be used for this dscp-value";
          type leafref {
            path "../../../../rewrite-rules/ip-remark-policy/name";
          }
        }
      }
    }
  }

  grouping ethernet-classifier {
    list dot1p-policy {
      if-feature "srl-feat:dot1p-classifier-rewrite";
      key "name";
      leaf name {
        type srl_nokia-comm:name;
        description
          "User-configured name for a 802.1p prioriy code point mapping policy

           The name 'default' is reserved for the system default dot1p mapping policy.";
      }
      list dot1p {
        key "value";
        leaf value {
          type dot1p-value;
        }
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class to which the dot1p value is mapped";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        leaf drop-probability {
          if-feature "not srl-feat:future-0-0";
          type drop-probability;
          description
            "The drop probability to which the dot1p value is mapped";
        }
        leaf profile {
          if-feature "srl-feat:future-0-0";
          type srl_nokia-comm:classify-profile;
          description
            "The profile to which the DSCP value is mapped";
        }
        leaf de-out-profile {
          if-feature "srl-feat:future-0-0";
          type boolean;
          default "true";
          description
            "The discard-eligibility to which the DSCP value is mapped";
        }
        leaf ip-remark-policy {
          if-feature "srl-feat:future-0-0";
          description
            "The ip-remark-policy to be used for this dscp-value";
          type leafref {
            path "../../../../rewrite-rules/ip-remark-policy/name";
          }
        }
      }
    }
  }

  grouping qos-rewrite-top {
    description
      "Top-level grouping for traffic marking (rewrite) policies";
    container rewrite-rules {
      srl_nokia-ext:first-released "19.11.1";
      uses dscp-rewrite;
      uses mpls-tc-rewrite;
      uses dot1p-rewrite;
      uses ip-remark {
        if-feature "srl-feat:future-0-0";
      }
    }
  }

  grouping dscp-rewrite {
    list dscp-policy {
      key "name";
      leaf name {
        type srl_nokia-comm:name;
        description
          "User-configured name for a DSCP rewrite policy.";
      }
      list map {
        key "forwarding-class";
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class name";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        list drop-probability {
          srl_nokia-ext:first-released "20.12.1";
          if-feature "not srl-feat:future-0-0";
          key "drop-probability";
          leaf drop-probability {
            type drop-probability;
            description
              "A drop probability level within the FC for which a different remarking is desired.";
          }
          leaf dscp {
            mandatory true;
            type srl_nokia-comm:dscp;
            description
              "The DSCP marking to be used for this specific drop-probability";
          }
        }
        list profile {
          if-feature "srl-feat:future-0-0";
          key "profile";
          leaf profile {
            type rewrite-profile;
            description
              "A packet profile within the FC for which a different remarking is desired.";
          }
          leaf dscp {
            mandatory true;
            type srl_nokia-comm:dscp;
            description
              "The DSCP marking to be used for this specific profile";
          }
        }
        leaf dscp {
          mandatory true;
          type srl_nokia-comm:dscp;
          description
            "The DSCP marking to be used for all packets associated with the FC, except those with a drop-probability-specific or profile-specific override.";
        }
      }
    }
  }

  grouping ip-remark {
    list ip-remark-policy {
      key "name";
      leaf name {
        type srl_nokia-comm:name;
        description
          "User defined ip-remark-policy name";
      }
      container in-plus {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
      }
      container in {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
      }
      container out {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
      }
      container exceed {
        choice dscp-or-precedence {
          case dscp {
            leaf dscp {
              type srl_nokia-comm:dscp;
              description
                "The DSCP marking to be used for this specific profile";
            }
          }
          case precedence {
            leaf precedence {
              description
                "The ip-precedence marking to be used for this specific profile";
              type uint8 {
                range "0..7";
              }
            }
          }
        }
      }
    }
  }

  grouping mpls-tc-rewrite {
    list mpls-traffic-class-policy {
      if-feature "srl-feat:jericho2 or srl-feat:jericho2cp or srl-feat:future-0-0";
      key "name";
      leaf name {
        type srl_nokia-comm:name;
        description
          "User-configured name for an MPLS traffic-class rewrite policy.";
      }
      list map {
        key "forwarding-class";
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class name";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        list drop-probability {
          srl_nokia-ext:first-released "21.6.1";
          if-feature "not srl-feat:future-0-0";
          key "drop-probability";
          leaf drop-probability {
            type drop-probability;
            description
              "A drop probability level within the FC for which a different remarking is desired.";
          }
          leaf traffic-class {
            mandatory true;
            type traffic-class;
            description
              "The MPLS traffic class marking to be used for this specific drop-probability";
          }
        }
        list profile {
          if-feature "srl-feat:future-0-0";
          key "profile";
          leaf profile {
            type rewrite-profile;
            description
              "A packet profile within the FC for which a different remarking is desired.";
          }
          leaf traffic-class {
            mandatory true;
            type traffic-class;
            description
              "The MPLS traffic class marking to be used for this specific profile";
          }
        }
        leaf traffic-class {
          mandatory true;
          type traffic-class;
          description
            "The MPLS traffic class marking to be used for all packets associated with the FC, except those with a drop-probability-specific or profile-specific override.";
        }
      }
    }
  }

  grouping dot1p-rewrite {
    list dot1p-policy {
      if-feature "srl-feat:dot1p-classifier-rewrite";
      key "name";
      leaf name {
        type srl_nokia-comm:name;
        description
          "User-configured name for an 802.1p priorty code point rewrite policy.";
      }
      list map {
        key "forwarding-class";
        leaf forwarding-class {
          type union {
            type leafref {
              path "/srl_nokia-qos:qos/srl_nokia-qos:forwarding-classes/srl_nokia-qos:forwarding-class/srl_nokia-qos:name";
            }
            type srl_nokia-comm:default-forwarding-class;
          }
          description
            "The forwarding class name";
          must "/srl_nokia-qos:qos/srl_nokia-qos:forwarding-classes/srl_nokia-qos:forwarding-class[srl_nokia-qos:name = current()]/srl_nokia-qos:name = current() or
                re-match(.,'fc[0-7]')" {
            error-message "forwarding-class doesn't exist";
          }
        }
        list drop-probability {
          srl_nokia-ext:first-released "20.12.1";
          if-feature "not srl-feat:future-0-0";
          key "drop-probability";
          leaf drop-probability {
            type drop-probability;
            description
              "A drop probability level within the FC for which a different remarking is desired.";
          }
          leaf dot1p {
            mandatory true;
            type dot1p-value;
            description
              "The dot1p marking to be used for this specific drop-probability";
          }
        }
        list profile {
          if-feature "srl-feat:future-0-0";
          key "profile";
          leaf profile {
            type rewrite-profile;
            description
              "A packet profile within the FC for which a different remarking is desired.";
          }
          leaf inner-dot1p {
            type dot1p-value;
            description
              "The inner-dot1p marking to be used for this specific profile";
          }
          leaf outer-dot1p {
            type dot1p-value;
            description
              "The outer-dot1p marking to be used for this specific profile";
          }
        }
        leaf dot1p {
          if-feature "not srl-feat:future-0-0";
          mandatory true;
          type dot1p-value;
          description
            "The dot1p marking to be used for all packets associated with the FC, except those with a drop-probability-specific or profile-specific override.";
        }
        leaf inner-dot1p {
          if-feature "srl-feat:future-0-0";
          type dot1p-value;
          description
            "The inner-dot1p marking to be used for all packets associated with the FC, except those with a profile-specific override.";
        }
        leaf outer-dot1p {
          if-feature "srl-feat:future-0-0";
          type dot1p-value;
          description
            "The outer-dot1p marking to be used for all packets associated with the FC, except those with a profile-specific override.";
        }
        container inner-de-mark {
          if-feature "srl-feat:future-0-0";
          presence "inner-de-mark";
          description
            "Re-marking inner-vlan discard-eligibility bit for respecitve forwarding-class";
          leaf force {
            type boolean;
            description
              "Forcing the discard-eligibility bit to a given value.";
          }
        }
        container outer-de-mark {
          if-feature "srl-feat:future-0-0";
          presence "outer-de-mark";
          description
            "Re-marking outer-vlan discard-eligibility bit for respecitve forwarding-class";
          leaf force {
            type boolean;
            description
              "Forcing the discard-eligibility bit to a given value.";
          }
        }
      }
    }
  }

  grouping interface-qos {
    container qos {
      if-feature "not srl-feat:platform-7220-d1";
      srl_nokia-ext:first-released "19.11.1";
      presence "Enables configuration of QoS parameters for the interface";
      must "starts-with(../srl_nokia-if:name, 'ethernet') or starts-with(../srl_nokia-if:name, 'lag')" {
        error-message "QoS does not apply to this interface type";
      }
      must 'not(../srl_nokia-if:breakout-mode)' {
        error-message "QoS does not apply when breakout-mode is enabled";
      }
      container output {
        srl_nokia-fss-ext:schema-conversion "interfaceQosOutput";
        description
          "Container for QoS configuration that applies to outbound traffic through the port or LAG";
        container scheduler {
          srl_nokia-ext:first-released "20.12.1";
          if-feature "not srl-feat:future-0-0";
          description
            "Output traffic scheduler options";
          choice policy-or-nodes {
            case policy {
              leaf scheduler-policy {
                if-feature "srl-feat:scheduler-policies";
                description
                  "Reference to a scheduler policy to apply to output traffic through the port.";
                type leafref {
                  path "/srl_nokia-qos:qos/srl_nokia-qos:scheduler-policies/srl_nokia-qos:scheduler-policy/srl_nokia-qos:name";
                }
              }
            }
            case nodes {
              list tier {
                max-elements 1;
                description
                  "List of output traffic scheduler tiers or levels";
                key "level";
                leaf level {
                  type scheduler-level;
                  must '. = 1' {
                    error-message "Only one scheduler level supported";
                  }
                }
                list node {
                  max-elements 12;
                  description
                    "List of scheduler nodes at the specified scheduler level";
                  key "node-number";
                  leaf node-number {
                    description
                      "An identifier of the scheduler node. Within a scheduler tier, higher-numbered nodes are served before lower-numbererd nodes.";
                    type scheduler-node-id;
                  }
                  leaf strict-priority {
                    description
                      "A true value configures the node for strict priority scheduling, whether or not a weight is also configured.  When set to false the node is serviced using DWRR, even if the node does not have a configured weight; in this case the default weight value of 1 is used.";
                    type boolean;
                  }
                  leaf weight {
                    description
                      "The DWRR weight assigned to the scheduler node";
                    type uint8 {
                      range "1..127";
                    }
                    default "1";
                  }
                }
              }
            }
          }
        }
        list queue {
          srl_nokia-ext:first-released "19.11.1";
          description
            "List of queues";
          key "queue-name";
          leaf queue-name {
            type union {
              type leafref {
                path "/srl_nokia-qos:qos/srl_nokia-qos:queues/srl_nokia-qos:queue/srl_nokia-qos:name";
              }
              type srl_nokia-comm:default-queue-name;
            }
            description
              "The queue name";
            must "/srl_nokia-qos:qos/srl_nokia-qos:queues/srl_nokia-qos:queue[srl_nokia-qos:name=current()]/srl_nokia-qos:name = current() or
                  re-match(.,'unicast-[0-7]') or re-match(.,'multicast-[0-7]')" {
              error-message "queue doesn't exist";
            }
          }
          leaf-list forwarding-class {
            config false;
            type string;
            description
              "The list of forwarding classes that map to this queue.";
          }
          container active-queue-management {
            if-feature "not srl-feat:future-0-0";
            config false;
            srl_nokia-ext:first-released "20.12.1";
            list wred-slope {
              description
                "List of WRED slopes.";
              key "traffic-type drop-probability";
              leaf traffic-type {
                description
                  "The traffic type to which the WRED slope applies.";
                type enumeration {
                  enum tcp {
                    description
                      "Refers to IPv4/IPv6 packets with a protocol/next-header indicating a value of 6.";
                  }
                  enum non-tcp {
                    description
                      "Refers to all packets that are not IPv4/IPv6 packets with a protocol/next-header indicating a value of 6.";
                  }
                  enum all {
                    description
                      "Refers to all traffic, whether it is TCP or non-TCP.";
                  }
                }
              }
              leaf drop-probability {
                description
                  "The drop probability to which the WRED slope applies.";
                type drop-probability;
              }
              leaf slope-enabled {
                description
                  "Reads true if the slope is enabled.

                   A disabled slope has min-threshold-bytes = max-threshold-bytes = max-probability = 0";
                type boolean;
              }
              leaf min-threshold-bytes {
                type uint32;
                units "bytes";
                description
                  "The queue depth in bytes that corresponds to the WRED mininum threshold parameter.";
              }
              leaf max-threshold-bytes {
                type uint32;
                units "bytes";
                description
                  "The queue depth in bytes that corresponds to the WRED maximum threshold parameter.";
              }
              leaf max-probability {
                type srl_nokia-comm:percentage;
                description
                  "The maximum probability of dropping a packet (at or above the max-threshold).

                   On 7250 IXR-6/10 there can be a significant difference between the configured value and the operational value.";
              }
            }
            list ecn-slope {
              description
                "List of ECN slopes.";
              key "ecn-drop-probability";
              leaf ecn-drop-probability {
                description
                  "The drop probability to which the ECN slope applies.";
                type ecn-drop-probability;
              }
              leaf slope-enabled {
                description
                  "Reads true if the slope is enabled.

                   A disabled slope has min-threshold-bytes = max-threshold-bytes = max-probability = 0";
                type boolean;
              }
              leaf min-threshold-bytes {
                type uint32;
                units "bytes";
                description
                  "The queue depth in bytes that corresponds to the ECN mininum threshold parameter.";
              }
              leaf max-threshold-bytes {
                type uint32;
                units "bytes";
                description
                  "The queue depth in bytes that corresponds to the ECN maximum threshold parameter.";
              }
              leaf max-probability {
                type srl_nokia-comm:percentage;
                description
                  "The maximum probability of marking a packet (at or above the max-threshold).

                   On 7250 IXR-6/10 there can be a significant difference between the configured value and the operational value.";
              }
            }
          }
          container queue-depth {
            config false;
            srl_nokia-ext:first-released "20.12.1";
            leaf maximum-burst-size {
              type uint32;
              units "bytes";
              description
                "Maximum queue depth in bytes.";
            }
            leaf committed-burst-size {
              if-feature "srl-feat:future-0-0";
              type uint32;
              units "bytes";
              description
                "Committed queue lengt in bytes";
            }
            leaf last-high-threshold-time {
              if-feature "not (srl-feat:platform-7220-d5 or srl-feat:future-0-0)";
              description
                "The last time the queue depth exceeded the high-threshold in a rising direction.";
              type srl_nokia-comm:date-and-time;
            }
            leaf high-threshold-bytes {
              if-feature "not (srl-feat:platform-7220-d5 or srl-feat:future-0-0)";
              type uint32;
              units "bytes";
              description
                "The operational hardware value of the high threshold in bytes.";
            }
          }
          container scheduling {
            description
              "Container for queue scheduling parameters";
            leaf peak-rate-percent {
              srl_nokia-ext:first-released "20.6.1";
              type uint8 {
                range "1..100";
              }
              default "100";
              description
                "The maximum percentage of port bandwidth that is available to the traffic in this queue during the PIR scheduling loop. The default is 100.";
            }
            leaf peak-rate-bps {
              srl_nokia-ext:first-released "20.6.1";
              config false;
              type uint64;
              description
                "The actual/operational peak rate in bits per second.";
            }
            leaf strict-priority {
              if-feature "srl-feat:jericho2 or srl-feat:jericho2cp";
              type boolean;
              description
                "When set to true the queue is serviced as a strict priority queue, regardless of whether a weight is configured or its value. When set to false the queue is serviced using WRR, even if the queue does not have a configured weight; in this case the default weight value of 1 is used.

                 For unicast queues the implicit default value is true";
              must 'not(../../../scheduler/scheduler-policy)';
            }
            leaf weight {
              srl_nokia-ext:first-released "20.6.1";
              if-feature "srl-feat:jericho2 or srl-feat:jericho2cp";
              type uint8 {
                range "1..255";
              }
              description
                "Configures the relative weight of a DWRR queue.

                 For unicast queues the implicit default value is 1";
              must 'not(../../../scheduler/scheduler-policy)';
            }
            leaf scheduler-node {
              srl_nokia-ext:first-released "20.12.1";
              if-feature "not srl-feat:future-0-0";
              config false;
              description
                "The scheduler node to which the queue is connected. The mappings are fixed and not user-configurable.

                 J2:
                 unicast-0..unicast-7 -> node 1
                 multicast-0..multicast-7 -> node 0

                 TD3 (D2/D3/D5):
                 unicast-x -> node x
                 multicast-x -> node x

                 TH3:
                 unicast-0 -> node 1
                 unicast-1 -> node 2
                 unicast-2 -> node 4
                 unicast-3 -> node 5
                 unicast-4 -> node 7
                 unicast-5 -> node 8
                 unicast-6 -> node 10
                 unicast-7 -> node 11
                 multicast-0 -> node 0
                 multicast-1 -> node 3
                 multicast-2 -> node 6
                 multicast-3 -> node 9
                ";
              type leafref {
                  // https://github.com/openconfig/ygot/issues/733
                  // The in-memory schemaTree created by ygot during code generation
                  // erroneously contains choice/case identifiers as branches.
                  // Workaround is to include choice/case identifier in leafref paths.
                  path "../../../scheduler/policy-or-nodes/nodes/tier/node/node-number";
              }
            }
          }
          leaf template {
            srl_nokia-ext:first-released "20.12.1";
            if-feature "not srl-feat:future-0-0";
            if-feature "srl-feat:platform-7220-d2 or srl-feat:platform-7220-d3 or srl-feat:platform-7220-d5 or srl-feat:platform-7220-h2 or srl-feat:platform-7220-h3 or srl-feat:platform-7220-h4";
            type leafref {
              path "/srl_nokia-qos:qos/srl_nokia-qos:queue-templates/srl_nokia-qos:queue-template/srl_nokia-qos:name";
            }
            description
              "The name of a queue-template to apply to the queue.

               If a queue has no queue-template, the default queue-template is applied. The user cannot modify the default queue-template.";
          }
          leaf voq-template {
            srl_nokia-ext:first-released "20.12.1";
            if-feature "not srl-feat:future-0-0";
            if-feature "srl-feat:jericho2 or srl-feat:jericho2cp";
            type leafref {
              path "/srl_nokia-qos:qos/srl_nokia-qos:queue-templates/srl_nokia-qos:queue-template/srl_nokia-qos:name";
            }
            description
              "The name of a queue-template to apply to the set of associated VOQs.

               If a queue has no voq-template, the default queue-template is applied";
          }
        }
      }
    }
  }

  grouping queue-stats {
    container queue-statistics {
      srl_nokia-ext:first-released "19.11.1";
      if-feature "not srl-feat:platform-7220-d1";
      config false;
      list queue {
        description
          "List of  queues.";
        key "queue-name";
        leaf queue-name {
          type union {
            type leafref {
              path "/srl_nokia-qos:qos/srl_nokia-qos:queues/srl_nokia-qos:queue/srl_nokia-qos:name";
            }
            type srl_nokia-comm:default-queue-name;
          }
          description
            "The queue name";
        }
        leaf last-clear {
          type srl_nokia-comm:date-and-time-delta;
          description
            "Timestamp of the last time the statistics associated with this queue were cleared";
        }
        leaf transmitted-packets {
          if-feature "not srl-feat:future-0-0";
          type srl_nokia-comm:zero-based-counter64;
          description
            "Number of packets transmitted by the queue, including transit traffic and locally originated traffic.";
        }
        leaf transmitted-octets {
          if-feature "not srl-feat:future-0-0";
          type srl_nokia-comm:zero-based-counter64;
          description
            "Number of octets transmitted by the queue.

             Note that on IXR-6/10 this count is based on the ingress packet size including received MPLS labels plus the Ethernet encapsulation that was present at ingress; popped and pushed MPLS labels are not accounted for and neither is the difference, if any, between ingress and egress Ethernet encapsulation size.

             Note that on IXR-6e/10e this count is based on the ingress packet size minus terminated/popped MPLS labels minus the Ethernet encapsulation; pushed MPLS labels are not accounted for and neither is the egress Ethernet encapsulation.";
        }
        leaf final-dropped-packets {
          if-feature "not srl-feat:future-0-0";
          type srl_nokia-comm:zero-based-counter64;
          description
            "Number of packets dropped by the queue.

             On 7250-IXR (Jericho2-based) systems unicast packet drops related to egress port congestion should show up in the VOQ stats and not in this statistic.";
        }
        leaf final-dropped-octets {
          if-feature "not srl-feat:future-0-0";
          type srl_nokia-comm:zero-based-counter64;
          description
            "Number of octets dropped by the queue.

             On 7250-IXR (Jericho2-based) systems unicast packet drops related to egress port congestion should show up in the VOQ stats and not in this statistic.";
        }
        list virtual-output-queue {
          if-feature "srl-feat:jericho2 or srl-feat:jericho2cp";
          description
            "List of virtual output queues that can send traffic to this egress queue. The list always has one entry for each IMM slot in the chassis, even if one or more slots are empty.";
          key "slot";
          leaf slot {
            type uint8 {
              range "1..8";
            }
            description
              "The slot identifier for the virtual output queue.";
          }
          container queue-depth {
            config false;
            srl_nokia-ext:first-released "21.6.1";
            leaf last-high-threshold-time {
              description
                "The last time the depth of either VOQ associated with this slot exceeded the high-threshold in a rising direction.";
              type srl_nokia-comm:date-and-time;
            }
            leaf high-threshold-bytes {
              type uint32;
              units "bytes";
              description
                "The operational hardware value of the high threshold in bytes.";
            }
          }
          container forwarded-packets {
            srl_nokia-ext:first-released "20.12.1";
            leaf low-drop-probability {
              type srl_nokia-comm:zero-based-counter64;
              description
                "The number of unicast packets transmitted from the VOQ to the egress queue that were classified as low drop-probability. This reads 0 when the IMM associated with the VOQ is not inserted and it resets to 0 whenever the IMM associated with the VOQ is removed.";
            }
            leaf medium-drop-probability {
              type srl_nokia-comm:zero-based-counter64;
              description
                "The number of unicast packets transmitted from the VOQ to the egress queue that were classified as medium drop-probability. This reads 0 when the IMM associated with the VOQ is not inserted and it resets to 0 whenever the IMM associated with the VOQ is removed.";
            }
            leaf high-drop-probability {
              type srl_nokia-comm:zero-based-counter64;
              description
                "The number of unicast packets transmitted from the VOQ to the egress queue that were classified as high drop-probability. This reads 0 when the IMM associated with the VOQ is not inserted and it resets to 0 whenever the IMM associated with the VOQ is removed.";
            }
          }
          container forwarded-octets {
            srl_nokia-ext:first-released "20.12.1";
            leaf low-drop-probability {
              type srl_nokia-comm:zero-based-counter64;
              description
                "The number of octets in unicast packets transmitted from the VOQ to the egress queue that were classified as low drop-probability. This reads 0 when the IMM associated with the VOQ is not inserted and it resets to 0 whenever the IMM associated with the VOQ is removed.";
            }
            leaf medium-drop-probability {
              type srl_nokia-comm:zero-based-counter64;
              description
                "The number of octets in unicast packets transmitted from the VOQ to the egress queue that were classified as medium drop-probability. This reads 0 when the IMM associated with the VOQ is not inserted and it resets to 0 whenever the IMM associated with the VOQ is removed.";
            }
            leaf high-drop-probability {
              type srl_nokia-comm:zero-based-counter64;
              description
                "The number of octets in unicast packets transmitted from the VOQ to the egress queue that were classified as high drop-probability. This reads 0 when the IMM associated with the VOQ is not inserted and it resets to 0 whenever the IMM associated with the VOQ is removed.";
            }
          }
          container dropped-packets {
            srl_nokia-ext:first-released "20.12.1";
            leaf low-drop-probability {
              type srl_nokia-comm:zero-based-counter64;
              description
                "The number of unicast packets dropped in the VOQ due to the congestion at the egress port/queue that were classified as low drop-probability. This reads 0 when the IMM associated with the VOQ is not inserted and it resets to 0 whenever the IMM associated with the VOQ is removed.";
            }
            leaf medium-drop-probability {
              type srl_nokia-comm:zero-based-counter64;
              description
                "The number of unicast packets dropped in the VOQ due to the congestion at the egress port/queue that were classified as medium drop-probability. This reads 0 when the IMM associated with the VOQ is not inserted and it resets to 0 whenever the IMM associated with the VOQ is removed.";
            }
            leaf high-drop-probability {
              type srl_nokia-comm:zero-based-counter64;
              description
                "The number of unicast packets dropped in the VOQ due to the congestion at the egress port/queue that were classified as high drop-probability. This reads 0 when the IMM associated with the VOQ is not inserted and it resets to 0 whenever the IMM associated with the VOQ is removed.";
            }
          }
          container dropped-octets {
            srl_nokia-ext:first-released "20.12.1";
            leaf low-drop-probability {
              type srl_nokia-comm:zero-based-counter64;
              description
                "The number of octets in unicast packets dropped in the VOQ due to the congestion at the egress port/queue that were classified as low drop-probability. This reads 0 when the IMM associated with the VOQ is not inserted and it resets to 0 whenever the IMM associated with the VOQ is removed.";
            }
            leaf medium-drop-probability {
              type srl_nokia-comm:zero-based-counter64;
              description
                "The number of octets in unicast packets dropped in the VOQ due to the congestion at the egress port/queue that were classified as medium drop-probability. This reads 0 when the IMM associated with the VOQ is not inserted and it resets to 0 whenever the IMM associated with the VOQ is removed.";
            }
            leaf high-drop-probability {
              type srl_nokia-comm:zero-based-counter64;
              description
                "The number of octets in unicast packets dropped in the VOQ due to the congestion at the egress port/queue that were classified as high drop-probability. This reads 0 when the IMM associated with the VOQ is not inserted and it resets to 0 whenever the IMM associated with the VOQ is removed.";
            }
          }
        }
        leaf transmitted-in-packets {
          if-feature "srl-feat:future-0-0";
          type srl_nokia-comm:zero-based-counter64;
          description
            "Number of packets marked with In or InPlus profile transmitted by the queue, including transit traffic and locally originated traffic.";
        }
        leaf transmitted-in-octets {
          if-feature "srl-feat:future-0-0";
          type srl_nokia-comm:zero-based-counter64;
          description
            "Number of octets marked with In or InPlus profile transmitted by the queue, including transit traffic and locally originated traffic.";
        }
        leaf dropped-in-packets {
          if-feature "srl-feat:future-0-0";
          type srl_nokia-comm:zero-based-counter64;
          description
            "Number of packets marked with In or InPlus profile transmitted by the queue dropped by the queue.";
        }
        leaf dropped-in-octets {
          if-feature "srl-feat:future-0-0";
          type srl_nokia-comm:zero-based-counter64;
          description
            "Number of octets marked with In or InPlus profile transmitted by the queue dropped by the queue.";
        }
        leaf transmitted-inplus-packets {
          if-feature "srl-feat:future-0-0";
          type srl_nokia-comm:zero-based-counter64;
          description
            "Number of packets marked with In or InPlus profile transmitted by the queue, including transit traffic and locally originated traffic.";
        }
        leaf transmitted-inplus-octets {
          if-feature "srl-feat:future-0-0";
          type srl_nokia-comm:zero-based-counter64;
          description
            "Number of octets marked with In or InPlus profile transmitted by the queue, including transit traffic and locally originated traffic.";
        }
        leaf dropped-inplus-packets {
          if-feature "srl-feat:future-0-0";
          type srl_nokia-comm:zero-based-counter64;
          description
            "Number of packets marked with In or InPlus profile transmitted by the queue dropped by the queue.";
        }
        leaf dropped-inplus-octets {
          if-feature "srl-feat:future-0-0";
          type srl_nokia-comm:zero-based-counter64;
          description
            "Number of octets marked with In or InPlus profile transmitted by the queue dropped by the queue.";
        }
        leaf transmitted-out-packets {
          if-feature "srl-feat:future-0-0";
          type srl_nokia-comm:zero-based-counter64;
          description
            "Number of packets marked with Out profile transmitted by the queue, including transit traffic and locally originated traffic.";
        }
        leaf transmitted-out-octets {
          if-feature "srl-feat:future-0-0";
          type srl_nokia-comm:zero-based-counter64;
          description
            "Number of octets marked with Out profile transmitted by the queue, including transit traffic and locally originated traffic.";
        }
        leaf dropped-out-packets {
          if-feature "srl-feat:future-0-0";
          type srl_nokia-comm:zero-based-counter64;
          description
            "Number of packets marked with Out profile transmitted by the queue dropped by the queue.";
        }
        leaf dropped-out-octets {
          if-feature "srl-feat:future-0-0";
          type srl_nokia-comm:zero-based-counter64;
          description
            "Number of octets marked with Out profile transmitted by the queue dropped by the queue.";
        }
        leaf transmitted-exceed-packets {
          if-feature "srl-feat:future-0-0";
          type srl_nokia-comm:zero-based-counter64;
          description
            "Number of packets marked with Exceed profile transmitted by the queue, including transit traffic and locally originated traffic.";
        }
        leaf transmitted-exceed-octets {
          if-feature "srl-feat:future-0-0";
          type srl_nokia-comm:zero-based-counter64;
          description
            "Number of octets marked with Exceed profile transmitted by the queue, including transit traffic and locally originated traffic.";
        }
        leaf dropped-exceed-packets {
          if-feature "srl-feat:future-0-0";
          type srl_nokia-comm:zero-based-counter64;
          description
            "Number of packets marked with Exceed profile transmitted by the queue dropped by the queue.";
        }
        leaf dropped-exceed-octets {
          if-feature "srl-feat:future-0-0";
          type srl_nokia-comm:zero-based-counter64;
          description
            "Number of octets marked with Out profile transmitted by the queue dropped by the queue.";
        }
      }
    }
  }

  grouping subinterface-qos {
    container qos {
      srl_nokia-ext:first-released "19.11.1";
      if-feature "not srl-feat:platform-7220-d1";
      container input {
        container policers {
          if-feature "srl-feat:ingress-subif-policing";
          description
            "Container with information about the policers applied to input traffic on the subinterface.";
          leaf policer-template {
            must "not(starts-with(../../../../../srl_nokia-if:name,'irb'))" {
              error-message "Not supported on IRB interfaces";
            }
            must "../../../../srl_nokia-if:type != 'srl_nokia-if:local-mirror-dest'" {
              error-message "policer not allowed on subinterface with type local-mirror-dest";
            }
            description
              "The name of the policer template applied to input traffic on the subinterface

               If this is configured but no value is displayed in state information then there were insufficient resources to completely apply the template.";
            type leafref {
              path "/srl_nokia-qos:qos/srl_nokia-qos:policer-templates/srl_nokia-qos:policer-template/srl_nokia-qos:name";
            }
          }
          list policer {
            config false;
            description
              "The list of policer instances belonging to the template definition.";
            key "sequence-id";
            leaf sequence-id {
              type uint32 {
                range "1..65535";
              }
              description
                "Policer sequeunce-id";
            }
            uses srl_nokia-qos-policers:policer-instance-state;
          }
        }
        container classifiers {
          srl_nokia-fss-ext:schema-conversion "subinterfaceQosInputClassifiers";
          leaf default-forwarding-class {
            description
              "The default forwarding class for packets arriving on this subinterface that do not match any classification rule.";
            type union {
              type leafref {
                path "/srl_nokia-qos:qos/srl_nokia-qos:forwarding-classes/srl_nokia-qos:forwarding-class/srl_nokia-qos:name";
              }
              type srl_nokia-comm:default-forwarding-class;
            }
            must "/srl_nokia-qos:qos/srl_nokia-qos:forwarding-classes/srl_nokia-qos:forwarding-class[srl_nokia-qos:name = current()]/srl_nokia-qos:name = current() or
                  re-match(.,'fc[0-7]')" {
              error-message "forwarding-class doesn't exist";
            }
            must "../../../../srl_nokia-if:type = 'srl_nokia-if:bridged'" {
              error-message "default-forwarding-class allowed with type bridged only";
              srl_nokia-ext:if-feature "not srl_nokia-features:fp5-c";
            }
          }
          leaf default-drop-probability {
            if-feature "not srl-feat:future-0-0";
            description
              "The default drop-probability for packets arriving on this subinterface that do not match any classification rule.";
            type drop-probability;
            must "../../../../srl_nokia-if:type = 'srl_nokia-if:bridged'" {
              error-message "default-drop-probability allowed with type bridged only";
            }
          }
          leaf default-profile {
            if-feature "srl-feat:future-0-0";
            description
              "The default profile for packets arriving on this subinterface that do not match any classification rule.";
            type srl_nokia-comm:classify-profile;
          }
          leaf ipv4-dscp-policy {
            if-feature "srl-feat:jericho2 or srl-feat:jericho2cp";
            type leafref {
              path "/srl_nokia-qos:qos/srl_nokia-qos:classifiers/srl_nokia-qos:dscp-policy/srl_nokia-qos:name";
            }
            description
              "Reference to the name of a DSCP mapping policy that applies only to IPv4 traffic.";
          }
          leaf ipv6-dscp-policy {
            if-feature "srl-feat:jericho2 or srl-feat:jericho2cp";
            type leafref {
              path "/srl_nokia-qos:qos/srl_nokia-qos:classifiers/srl_nokia-qos:dscp-policy/srl_nokia-qos:name";
            }
            description
              "Reference to the name of a DSCP mapping policy that applies only to IPv6 traffic.";
          }
          leaf dscp-policy {
            srl_nokia-ext:first-released "20.6.1";
            if-feature "srl-feat:platform-7220-d2 or srl-feat:platform-7220-d3 or srl-feat:platform-7220-d5 or srl-feat:tomahawk3 or srl-feat:tomahawk4 or srl-feat:tomahawk4 or srl-feat:future-0-0";
            type leafref {
              path "/srl_nokia-qos:qos/srl_nokia-qos:classifiers/srl_nokia-qos:dscp-policy/srl_nokia-qos:name";
            }
            description
              "Reference to the name of a DSCP mapping policy that applies to both IPv4 and IPv6 traffic.";
          }
          leaf dot1p-policy {
            srl_nokia-ext:first-released "22.6.1";
            if-feature "srl-feat:dot1p-classifier-rewrite";
            type leafref {
              path "/srl_nokia-qos:qos/srl_nokia-qos:classifiers/srl_nokia-qos:dot1p-policy/srl_nokia-qos:name";
            }
            description
              "Reference to the name of a dot1p mapping policy.";
            must "../../../../srl_nokia-if:type = 'srl_nokia-if:bridged'" {
              error-message "dot1p classifiers allowed with type bridged only";
            }
          }
          leaf mpls-traffic-class-policy {
            if-feature "srl-feat:jericho2 or srl-feat:jericho2cp or srl-feat:future-0-0";
            type leafref {
              path "/srl_nokia-qos:qos/srl_nokia-qos:classifiers/srl_nokia-qos:mpls-traffic-class-policy/name";
            }
            description
              "Reference to the name of an MPLS traffic-class mapping policy";
          }
          leaf ler-use-dscp {
            if-feature "srl-feat:future-0-0";
            description
              "Enables short-pipe model for all lsp-bindings terminated on the subinterface";
            type boolean;
            default "false";
          }
          leaf match-qinq-dot1p {
            if-feature "srl-feat:future-0-0";
            description
              "Defines which dot1p bits will be used for dot1p-classification in case of QinQ encapsulation.";
            type enumeration {
              enum top;
              enum bottom;
            }
            default "top";
          }
          leaf tos-marking-state {
            if-feature "srl-feat:future-0-0";
            description
              "Defines whether given subinterface is considered as trusted/untrusted for remarking purpose.";
            type enumeration {
              enum trusted;
              enum untrusted;
            }
            default "trusted";
          }
        }
      }
      container output {
        srl_nokia-ext:first-released "19.11.1";
        leaf dscp-reclassify-policy {
          if-feature "srl-feat:future-0-0";
          type leafref {
            path "/srl_nokia-qos:qos/srl_nokia-qos:classifiers/srl_nokia-qos:dscp-reclassify-policy/srl_nokia-qos:name";
          }
          description
            "Reference to egress dscp-reclassification policy.";
        }
        leaf out-class-map {
          if-feature "srl-feat:future-0-0";
          type leafref {
            path "/srl_nokia-qos:qos/srl_nokia-qos:out-class-map/srl_nokia-qos:name";
          }
          description
            "Reference to the name of out-class-map that applies to subinterface";
        }
        container queues {
          if-feature "srl-feat:future-0-0";
          config false;
          description
            "Container dispaying state information related to output queues at subinterface level";
          list queue {
            description
              "List of output-queues";
            key "queue-name";
            leaf queue-name {
              type union {
                type leafref {
                  path "/srl_nokia-qos:qos/srl_nokia-qos:queues/srl_nokia-qos:queue/srl_nokia-qos:name";
                }
                type srl_nokia-comm:default-queue-name;
              }
              description
                "The output queue-name";
            }
            leaf-list forwarding-class {
              config false;
              type string;
              description
                "The list of forwarding classes that map to this queue.";
            }
            container queue-depth {
              description
                "Container for output-queue depth parameters";
              leaf committed-burst-size-bytes {
                config false;
                type uint32;
                units "bytes";
                description
                  "Operational committed queue depth in bytes.";
              }
              leaf maximum-burst-size-bytes {
                config false;
                type uint32;
                units "bytes";
                description
                  "Operational maximum queue depth in bytes.";
              }
            }
            container scheduling {
              description
                "Container for queue scheduling parameters";
              leaf peak-rate-bps {
                config false;
                type uint64;
                description
                  "The actual/operational peak rate in bits per second.";
              }
              leaf scheduling-class {
                config false;
                description
                  "The scheduling-class for output-queue";
                type uint8 {
                  range "0..7";
                }
              }
              leaf weight {
                config false;
                type uint8 {
                  range "1..127";
                }
                description
                  "Configures the relative weight of output-queue.";
              }
            }
          }
          uses queue-stats;
                }   //containerqueues 
        container rewrite-rules {
          srl_nokia-fss-ext:schema-conversion "subinterfaceQosOutputRewriteRules";
          leaf ipv4-dscp-policy {
            if-feature "srl-feat:jericho2 or srl-feat:jericho2cp";
            type leafref {
              path "/srl_nokia-qos:qos/srl_nokia-qos:rewrite-rules/srl_nokia-qos:dscp-policy/srl_nokia-qos:name";
            }
            description
              "Reference to the name of a DSCP rewrite-rule policy that applies only to IPv4 traffic.";
          }
          leaf ipv6-dscp-policy {
            if-feature "srl-feat:jericho2 or srl-feat:jericho2cp";
            type leafref {
              path "/srl_nokia-qos:qos/srl_nokia-qos:rewrite-rules/srl_nokia-qos:dscp-policy/srl_nokia-qos:name";
            }
            description
              "Reference to the name of a DSCP rewrite-rule policy that applies only to IPv6 traffic.";
          }
          leaf dscp-policy {
            srl_nokia-ext:first-released "20.6.1";
            if-feature "srl-feat:platform-7220-d2 or srl-feat:platform-7220-d3 or srl-feat:platform-7220-d5 or srl-feat:tomahawk3 or srl-feat:tomahawk4 or srl-feat:tomahawk4 or srl-feat:future-0-0";
            type leafref {
              path "/srl_nokia-qos:qos/srl_nokia-qos:rewrite-rules/srl_nokia-qos:dscp-policy/srl_nokia-qos:name";
            }
            description
              "Reference to the name of a DSCP rewrite-rule policy that applies to both IPv4 and IPv6 traffic.";
            must "../../../../srl_nokia-if:type != 'srl_nokia-if:bridged'" {
              error-message "rewrite-rules not allowed with type bridged";
            }
          }
          leaf dot1p-policy {
            srl_nokia-ext:first-released "22.6.1";
            if-feature "srl-feat:dot1p-classifier-rewrite";
            type leafref {
              path "/srl_nokia-qos:qos/srl_nokia-qos:rewrite-rules/srl_nokia-qos:dot1p-policy/srl_nokia-qos:name";
            }
            description
              "Reference to the name of a dot1p rewrite policy.";
            must '../../../../../srl_nokia-if:vlan-tagging = true()' {
              error-message "rewrite-rules not allowed on untagged subinterface ";
            }
            must "not(starts-with(../../../../../srl_nokia-if:name,'lo'))" {
              error-message "rewrite-rules not allowed on loopback subinterface";
            }
          }
          leaf mpls-traffic-class-policy {
            if-feature "srl-feat:jericho2 or srl-feat:jericho2cp or srl-feat:future-0-0";
            type leafref {
              path "/srl_nokia-qos:qos/srl_nokia-qos:rewrite-rules/srl_nokia-qos:mpls-traffic-class-policy/name";
            }
            description
              "Reference to the name of an MPLS traffic-class rewrite-rule policy.";
          }
          container remarking {
            if-feature "srl-feat:future-0-0";
            presence "remarking";
            leaf force-remark-trusted {
              type boolean;
              default "false";
              description
                "Enables remarking packets incomming on trusted interfaces.";
            }
          }
          leaf qinq-mark-top-only {
            if-feature "srl-feat:future-0-0";
            type boolean;
            default "true";
            description
              "Enables remarking only outer-dot1p bits";
          }
        }
      }
    }
  }

  uses qos-top;

  augment "/srl_nokia-if:interface" {
    uses interface-qos;
    uses queue-stats;
  }

  augment "/srl_nokia-if:interface/srl_nokia-if:subinterface" {
    uses subinterface-qos;
  }
}
