module srl_nokia-fsp-workload-matchGroup {
    yang-version "1";

    // namespace
    namespace "urn:srl_nokia/fsp-workload-matchGroup";
    prefix "srl_nokia-fsp-workload-matchGroup";

    import srl_nokia-fsp { prefix srl-fsp; }
    import srl_nokia-common { prefix srl_nokia-comm; }
    import srl_nokia-packet-match-types { prefix srl_nokia-pkt-match-types; }

    description
      "This module defines FSP WorkLoad TemplateProfile";

    revision "2020-08-11" {
        description
          "Initial revision";
        reference
          "TBD";
    }

    grouping common-ipv4-filter-entry-match-config {
        leaf-list ipv4-address {
            description
                "A packet matches this condition if its IP address is within the specified IPv4 prefix.";
            type srl_nokia-comm:ipv4-prefix;
        }
        // container match {
        //     description
        //         "Container for the conditions that determine whether a packet matches this entry";
        //     leaf fragment {
        //         type boolean;
        //         description
        //             "Match an IPv4 fragment

        //             A packet matches the true condition if the IPv4 header indicates that the fragment-offset is zero and and the more-fragments bit is 1 or if the IPv4 header indicates that the fragment-offset is greater than 0. A packet matches the false condition if it is unfragmented.";
        //     }
        //     leaf first-fragment {
        //         type boolean;
        //         description
        //             "Match the first fragment of an IPv4 datagram

        //             A packet matches the true condition if the IPv4 header indicates that the fragment-offset is zero and and the more-fragments bit is 1. It is not valid to configure this leaf without configuring a match value for the fragment leaf.";
        //     }
        //     container icmp {
        //         description
        //             "A packet matches this condition if its ICMP type and code matches one of the specified combinations

        //             The rule should also have a condition that the IP protocol equals 1 (ICMP) in order for this to be interpreted correctly.";
        //         leaf type {
        //             description "Match a single ICMP type value.";
        //             type srl_nokia-pkt-match-types:icmp-type;
        //         }
        //         leaf-list code {
        //             description
        //                 "Match if the ICMP code value is any value in the list

        //                 Requires ICMP type to be specified because codes are type dependent.";
        //             type uint8;
        //         }
        //     }
        //     leaf protocol {
        //         description
        //             "An IPv4 packet matches this condition if its IP protocol type field matches the specified value";
        //         type srl_nokia-pkt-match-types:ip-protocol-type;
        //     }

        //     container port {
        //         description
        //             "A packet matches this condition if its TCP or UDP port number matches the value or range that is specified

        //             The rule should also have a condition that the IP protocol equals 6 (TCP) or 17 (UDP) in order for this to be interpreted correctly.";
        //         leaf operator {
        //             description
        //                 "Comparison operator

        //                 eq = equal
        //                 ge = greater than or equal to
        //                 le = less than or equal to";
        //             type srl_nokia-pkt-match-types:operator;
        //         }
        //         leaf value {
        //             description "A port number";
        //             type srl_nokia-pkt-match-types:l4-port-type;
        //         }
        //         container range {
        //             description
        //                 "Container used to specify a contiguous range of TCP/UDP port numbers";
        //             leaf start {
        //                 type srl_nokia-pkt-match-types:l4-port-type;
        //                 description "The starting port number to include in the range";
        //             }
        //             leaf end {
        //                 type srl_nokia-pkt-match-types:l4-port-type;
        //                 description "The ending port number to include in the range";
        //             }
        //         }
        //     }
        //     leaf tcp-flags {
        //         type string {
        //             pattern '(\(|\)|&|\||!|ack|rst|syn)+';
        //         }
        //         description
        //             "A logical expression using the &, | and ! logical operators and the TCP flag names: rst, syn and ack.";
        //     }
        // }
    }

    grouping common-ipv6-filter-entry-match-config {
        leaf-list ipv6-address {
            description
                "A packet matches this condition if its IP address is within the specified IPv6 prefix";
            type srl_nokia-comm:ipv6-prefix;
        }
        // container match {
        //     description
        //         "Container for the conditions that determine whether a packet matches this entry";
        //     container icmp6 {
        //         description
        //             "A packet matches this condition if its ICMPv6 type and code matches one of the specified combinations

        //             The rule should also have a condition that the next-header value equals 58 (ICMPv6) in order for this to be interpreted correctly.";
        //         leaf type {
        //             description "Match a single ICMPv6 type value";
        //             type srl_nokia-pkt-match-types:icmp6-type;
        //         }
        //         leaf-list code {
        //             description
        //                 "Match if the ICMPv6 code value is any value in the list

        //                 Requires ICMPv6 type to be specified because codes are type dependent.";
        //             type uint8;
        //         }
        //     }
        //     leaf next-header {
        //         description
        //             "An IPv6 packet matches this condition if its first next-header field (in the IPv6 fixed header) contains the specified value";
        //         type srl_nokia-pkt-match-types:ip-protocol-type;
        //     }
            
        //     container port {
        //         description
        //             "A packet matches this condition if its TCP or UDP port number matches the value or range that is specified

        //             The rule should also have a condition that the IP protocol equals 6 (TCP) or 17 (UDP) in order for this to be interpreted correctly.";
        //         leaf operator {
        //             description
        //                 "Comparison operator

        //                 eq = equal
        //                 ge = greater than or equal to
        //                 le = less than or equal to";
        //             type srl_nokia-pkt-match-types:operator;
        //         }
        //         leaf value {
        //             description "A port number";
        //             type srl_nokia-pkt-match-types:l4-port-type;
        //         }
        //         container range {
        //             description
        //                 "Container used to specify a contiguous range of TCP/UDP port numbers";
        //             leaf start {
        //                 type srl_nokia-pkt-match-types:l4-port-type;
        //                 description "The starting port number to include in the range";
        //             }
        //             leaf end {
        //                 type srl_nokia-pkt-match-types:l4-port-type;
        //                 description "The ending port number to include in the range";
        //             }
        //         }
        //     }
        //     leaf tcp-flags {
        //         type string {
        //             pattern '(\(|\)|&|\||!|ack|rst|syn)+';
        //         }
        //         description
        //             "A logical expression using the &, | and ! logical operators and the TCP flag names: rst, syn and ack.";
        //     }
        // }
    }


    grouping workload-ipv4matchGroup-entry {
        leaf name {
            type string {
                length "1..100";
                pattern "[A-Za-z0-9 !@#$%^&()|+=`~.,'_:;-]*";
            }
        }
        leaf description {
            type string;
        }
        container ipv4-match-entry {
            uses common-ipv4-filter-entry-match-config;
        }
        list ACLprofile {
            config false;
            key "name";
            leaf name {
                type string;
            }
        }
    }

     grouping workload-ipv6matchGroup-entry {
        leaf name {
            type string {
                length "1..100";
                pattern "[A-Za-z0-9 !@#$%^&()|+=`~.,'_:;-]*";
            }
        }
        leaf description {
            type string;
        }
        container ipv6-match-entry {
            uses common-ipv6-filter-entry-match-config;
        }
        list ACLprofile {
            config false;
            key "name";
            leaf name {
                type string;
            }
        }
    }

    grouping fsp-workload-matchGroup-top {
        list workload-ipv4matchGroup {
            key name;
            uses workload-ipv4matchGroup-entry;
        }
        list workload-ipv6matchGroup {
            key name;
            uses workload-ipv6matchGroup-entry;
        }
    }

    augment "/srl-fsp:fsp" {
        uses fsp-workload-matchGroup-top;
    }
}
