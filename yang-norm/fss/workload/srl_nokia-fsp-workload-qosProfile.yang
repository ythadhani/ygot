module srl_nokia-fsp-workload-qosProfile {
    yang-version "1";

    // namespace
    namespace "urn:srl_nokia_custom/fsp-workload-qosProfile";
    prefix "srl_nokia-fsp-workload-qosProfile";

    import srl_nokia-fsp {
        prefix srl-fsp;
    }
    import srl_nokia-fsp-common {
        prefix srl-fsp-common;
    }
    import srl_nokia-qos-custom {
        prefix srl_nokia-qos-custom;
    }

    description
      "This module defines FSP WorkLoad TemplateProfile";

    revision "2020-08-11" {
        description
          "Initial revision";
        reference
          "TBD";
    }

    grouping workload-qosProfile-entry {
        leaf name {
            type string {
                length "1..100";
                pattern "[A-Za-z0-9 !@#$%^&()|+=`~.,'_:;-]*";
            }
        }
        leaf profileType {
            type string;
        }
        leaf description {
            type string;
        }
        leaf workloadID {
            type string;
        }
        leaf version {
            type string;
        }
        container profile {
            uses srl_nokia-qos-custom:qos-top;
        }
        uses srl-fsp-common:ExternalID;
    }

    grouping fsp-workload-qosProfile-top {
        list workload-qosProfile {
            key name;
            uses workload-qosProfile-entry;
        }
    }

    augment "/srl-fsp:fsp" {
        uses fsp-workload-qosProfile-top;
    }
}
