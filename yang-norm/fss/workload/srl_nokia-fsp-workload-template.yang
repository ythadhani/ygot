module srl_nokia-fsp-workload-template {
    yang-version "1";

    // namespace
    namespace "urn:srl_nokia/fsp-workload-template";
    prefix "srl_nokia-fsp-workload-template";

    import srl_nokia-fsp {
        prefix srl-fsp;
    }
    import srl_nokia-fsp-common {
        prefix srl-fsp-common;
    }

    description
      "This module defines FSP workload template struct";

    revision "2020-01-02" {
        description
          "Initial revision";
        reference
          "TBD";
    }

    grouping workload-template-entry {
        leaf name {
            type string;
        }
        leaf description {
            type string;
        }
        leaf templateType {
            type srl-fsp-common:WorkloadIntentType;
        }
    }

    grouping fsp-workload-template-top {
        list workloadTemplate {
            key name;
            uses workload-template-entry;
        }
    }

    augment "/srl-fsp:fsp" {
        uses fsp-workload-template-top;
    }
}
