module srl_nokia-fsp-network-resources {
    yang-version "1";

    // namespace
    namespace "urn:srl_nokia/fsp-networkResources";
    prefix "srl_nokia-fsp-networkResources";

    import srl_nokia-fsp {
        prefix srl-fsp;
    }
    import srl_nokia-common {
        prefix srl-comm;
    }
    import srl_nokia-fsp-common {
        prefix srl-fsp-common;
    }
    import srl_nokia-fsp-profile-islCidr {
        prefix srl-fsp-profile-islCidr;
    }
    import srl_nokia-fsp-profile-routerID {
        prefix srl-fsp-profile-routerID;
    }
    import srl_nokia-fsp-profile-asn {
        prefix srl-fsp-profile-asn;
    }
    import srl_nokia-fsp-profile-mgmtcidr {
        prefix srl-fsp-profile-mgmtcidr;
    }
    import srl_nokia-fsp-profile-vni {
        prefix srl-fsp-profile-vni;
    }
    import srl_nokia-fsp-profile-evi {
        prefix srl-fsp-profile-evi;
    }    
    description
      "This module defines FSP network resources struct";

    revision "2022-06-27" {
        description
          "Initial revision";
        reference
          "TBD";
    }

    grouping network-resources-entry {
        leaf uuid {
            type string;
        }
        leaf name {
            type string;
        }
        leaf description {
            type string;
        }
        list asn {
            key "poolName";
            uses srl-fsp-profile-asn:ASNProfile-entry;
        }
    }

    container fsp-network-resources-top {
        uses network-resources-entry;
    }

    augment "/srl-fsp:fsp" {
        uses fsp-network-resources-top;
    }
}
