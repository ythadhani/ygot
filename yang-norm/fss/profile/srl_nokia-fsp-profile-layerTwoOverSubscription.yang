module srl_nokia-fsp-profile-layerTwoOverSubscription {
    yang-version 1;
    namespace "urn:srl_nokia/fsp-profile-layerTwoOverSubscription";
    prefix srl_nokia-fsp-profile-layerTwoOverSubscription;

    description "This module defines FSP layerTwoOverSubscription profile struct";

    revision 2020-01-02 {
        description
                "Initial revision";
    }

    grouping layerTwoOverSubscriptionProfile-entry {

        leaf overSubscriptionRatio {
            type string {
                pattern '[0-9]+:[0-9]+';
            }
        }
    }

    container fsp-profile-layerTwoOverSubscription {
        uses layerTwoOverSubscriptionProfile-entry;
    }
}
