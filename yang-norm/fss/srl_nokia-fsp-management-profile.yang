module srl_nokia-fss-management-profile {
     yang-version "1";

    // namespace
    namespace "urn:srl_nokia/fss-management-profile";
    prefix "srl_nokia-fss-management-profile";

    import srl_nokia-fsp {
        prefix srl-fsp;
    }

    import srl_nokia-fsp-common {
        prefix srl-fsp-common;
    }
    import srl_nokia-fsp-label {
        prefix srl-fsp-label;
    }
    import srl_nokia-extensions {
        prefix srl-ext;
    }

    description
        "This module defines FSS management profile";


    revision "2022-5-03" {
        description
                "Initial revision";
        reference "TBD";
    }
    
    // grouping fss-snmp-v1-v2c-entry {
    //     leaf community {
    //      // type srl-fsp-common:fss-secret;
    //       type string {
    //         srl-ext:generated-class-name "SecretKey";
    //       }
    //     }
    // }
    grouping fss-snmp-v3-entry {
        leaf privacyProtocol {
          type srl-fsp-common:SNMPPrivacyProtocol;
        }
        leaf securityLevel {
          type srl-fsp-common:SNMPSecurityLevel;
        }
        leaf authenticationProtocol{
          type srl-fsp-common:SNMPAuthenticationProtocol;
        }
        leaf user {
          type string;
        }
        leaf authenticationKeyPassword {
        //  type srl-fsp-common:fss-secret;
          type string {
            srl-ext:generated-class-name "SecretKey";
          }
        }
        leaf privacyKeyPassword {
        //  type srl-fsp-common:fss-secret;
          type string {
            srl-ext:generated-class-name "SecretKey";
          }
        }
    }

    grouping fss-snmp-profile-entry{
        description
            "management profile for snmp";
        leaf version {
          type srl-fsp-common:SNMPVersion;
        }
        leaf port {
          type uint32;
          default 161;
        }
        // container snmpV1-V2c {
        //  uses fss-snmp-v1-v2c-entry;
        // }
        container snmpV3 {
         uses fss-snmp-v3-entry;
        } 
    }

    grouping fss-gnmi-profile-entry{
        description
            "management profile for gnmi";
        leaf user {
          type string;
          default admin;
        }
        leaf password {
          //type srl-fsp-common:fss-secret;
          type string {
            srl-ext:generated-class-name "SecretKey";
          }
          default admin;
        }
        leaf port {
          type uint32;
          default 50052;
          config false;
        }
        leaf verifyTLScert {
          type boolean;
          default true;
          config false;
        }
        leaf trustAnchor {
          type string;
          config false;
        }
        leaf clientCert {
          type string;
          config false;
        }
    }

    grouping fss-management-profile-top {
        description "management-profile for FSS Data";
        container management-profile {
            leaf uuid {
              type string;
              config false;
            }
            leaf name {
              type string;
            }
            leaf description{
              type string;
            }
            leaf type {
              type srl-fsp-common:ManagementProfileType;
            }
            list labels {
              key "name value";
              uses srl-fsp-label:fsp-label-per-object-entry;
            }
            leaf isDefault {
              type boolean;
            }
            container gnmiProfile {
                uses fss-gnmi-profile-entry;
            }
            container snmpProfile {
                uses fss-snmp-profile-entry;
            }
        }
    }
    augment "/srl-fsp:fsp" {
        uses fss-management-profile-top;
    }
}
