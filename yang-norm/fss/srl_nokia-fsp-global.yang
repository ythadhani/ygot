module srl_nokia-fsp-global {
    yang-version "1";

    // namespace
    namespace "urn:srl_nokia/fsp-global";
    prefix "srl_nokia-fsp-global";
    
    import srl_nokia-fsp {prefix srl-fsp;}
    import srl_nokia-common {prefix srl-comm;}
    import srl_nokia-fsp-common {prefix srl-fsp-common;}
    import srl_nokia-fsp-profile-mgmtcidr {prefix srl-fsp-profile-mgmtcidr;}
    import srl_nokia-fsp-profile-islCidr {prefix srl-fsp-profile-islCidr;}
    import srl_nokia-fsp-profile-downlinkCidr {prefix srl-fsp-profile-downlinkCidr;}
    import srl_nokia-fsp-profile-routerID {prefix srl-fsp-profile-routerID;}
    import srl_nokia-fsp-profile-asn {prefix srl-fsp-profile-asn;}
    import srl_nokia-fsp-profile-globalCfg {prefix srl-fsp-profile-globalCfg;}


    description "This module defines FSP profile struct";

    revision "2020-01-02" {
        description
                "Initial revision";
        reference "TBD";
    }

    grouping Global-entry {
        container globalCfg {
            uses srl-fsp-profile-globalCfg:GlobalCfg-entry;
        }
    }

    grouping fsp-global-top {
        container global {
            uses Global-entry;
        }
    }

    augment "/srl-fsp:fsp" {
        uses fsp-global-top;
    }
}
